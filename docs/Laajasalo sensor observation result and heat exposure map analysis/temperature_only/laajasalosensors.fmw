FME workspace laajasalosensors.fmw

Parameters:
- SourceDataset_GEOTIFF = /Users/andreas.andra/LaajasaloSensors/Urban Heat Exposure Index.tif   # Source GeoTIFF File(s) or URL(s)
- SourceDataset_GEOJSON = /Users/andreas.andra/LaajasaloSensors/r4c_laajasalo_sensors_4326.geojson   # Source GeoJSON File or URL
- DestDataset_GEOJSON = /Users/andreas.andra/LaajasaloSensors/SensorsVsExposure.json   # Destination GeoJSON File
- SourceDataset_PARQUET = /Users/andreas.andra/LaajasaloSensors/r4c_all.parquet   # Source Parquet File(s)

Readers:
- GEOTIFF_1: GEOTIFF from $(SourceDataset_GEOTIFF)
- GEOJSON_1: GEOJSON from $(SourceDataset_GEOJSON)
- PARQUET_1: PARQUET from $(SourceDataset_PARQUET)

Writers:
- GEOJSON_2: GEOJSON to $(DestDataset_GEOJSON)

r4c_laajasalo_sensors (reader GEOJSON_1)
    attributes: id string, Address string, Asennus string
    -> Match_sensor_to_exposure_map [Candidate]
GEOTIFF (reader GEOTIFF_1)
    -> RasterToPolygonCoercer
RasterToPolygonCoercer
    EXTRACT_NODATA = No
    LABEL_ATTRIBUTE = _label
    PRESERVE_ATTRIBUTES = Yes
    POLYGONS -> Reproject_to_WGS84
Reproject_to_WGS84: Reprojector
    DEST = LL-WGS84
    INTERPOLATION_TYPE_NAME = Nearest Neighbor
    RASTER_CELL_SIZE = Preserve Cells
    RASTER_TOLERANCE = 0.0
    REPROJECTED -> Match_sensor_to_exposure_map [Filter]
Match_sensor_to_exposure_map: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS
    USE_BOUNDING_BOX = No
    PASSED -> AttributeRemover
AttributeRemover
    REMOVE_ATTRS = _predicate,Asennus,fme_basename
    -> AttributeRenamer
AttributeRenamer
    ATTR_TABLE:
      RENAME_SET_DEFAULT _label > heatExposureIndex
      RENAME_SET_DEFAULT Address > address
    MISSING_INPUT_ATTRS = REMOVE
    -> Join_on_ID [RIGHT]
r4c_all (reader PARQUET_1)
    attributes: dev-id string, batt double, temprh_rh double, temprh_temp double, time timestamp
    -> Exclude_observations_outside_timeframe
Exclude_observations_outside_timeframe: Tester
    BOOL_OP = OR
    TEST_CLAUSE = TEST @Value(time) > 20230628173200
    TEST_MODE = TEST
    PASSED -> AttributeRemover_2
AttributeRemover_2
    REMOVE_ATTRS = batt,time
    -> Calculate_T_and_RH_mean_values
Calculate_T_and_RH_mean_values: StatisticsCalculator
    CALCULATION_MODE = NUMERIC
    FEAT_STATS = temprh_rh,NUMERIC_MODE,,,,,MEAN,,,,,,,,;temprh_temp,NUMERIC_MODE,,,,,MEAN,,,,,,,,
    GROUP_BY = dev-id
    SUMMARY -> Extract_id
Extract_id: SubstringExtractor
    END = -1
    RESULT_ATTR = id
    SRC_STRING = @Value(dev-id)
    START = 11
    -> Join_on_ID [LEFT]
Join_on_ID: FeatureJoiner
    ATTR_CONFLICT_RES = Prefer Left
    GEOMETRY_HANDLING = Prefer Left
    JOIN_KEYS = id id AUTO
    JOIN_MODE = Inner
    JOINED -> Calculate_Steadman_heat_index_in_F
Calculate_Steadman_heat_index_in_F: AttributeManager
    ATTR_TABLE:
      SET_TO steadmanIndexF = @mult(0.5, @add(
            @add(
                @add(
                    @add(
                        @mult(
                            @add(
                                @mult(@Value(temprh_temp.mean), 9/5),
                                32
                            ),
                            1.0
                        ),
                        61.0
                    ),
                    @mult(
                        @sub(
                            @add(
                                @mult(@Value(temprh_temp.mean), 9/5),
                                32
                            ),
                            68.0
                        ),
                        1.2
                    )
                ),
                @mult(
                    @Value(temprh_rh.mean),
                    0.094
                )
            )
        ))
    -> Transform_Index_from_F_to_C_degrees
Transform_Index_from_F_to_C_degrees: AttributeManager
    ATTR_TABLE:
      RENAME_SET_VALUE steadmanIndexF
      SET_TO steadmanIndexC = @mult(@div(@sub(@Value(steadmanIndexF), 32), 9), 5)
    -> AttributeRemover_3
AttributeRemover_3
    REMOVE_ATTRS = dev-id,steadmanIndexF
    -> r4c_laajasalo_sensors (writer GEOJSON_2)
r4c_laajasalo_sensors (writer GEOJSON_2)
    attributes: temprh_rh.mean float, temprh_temp.mean float, id string, heatExposureIndex string, address string, steadmanIndexC string
